module sorespo-rfs {
    yang-version "1.1";
    namespace "http://example.com/sorespo-rfs";
    prefix "sorespo-rfs";

    import stratoweave-rfs {
        prefix sw-rfs;
    }
    import ietf-inet-types {
      prefix inet;
    }
    import stratoweave {
      prefix sw;
    }

    augment "/sw-rfs:rfs" {
        container base-config {

            sw:rfs-transform sorespo.rfs.BaseConfig;

            leaf role {
                type string;
            }

            leaf ipv4-address {
                type string;
                mandatory true;
            }

            leaf ipv6-address {
                type string;
                mandatory true;
            }

            leaf asn {
                type inet:as-number;
                mandatory true;
            }

            leaf ibgp-authentication-key {
                type string;
                mandatory true;
            }
        }

        list backbone-interface {
            key name;

            sw:rfs-transform sorespo.rfs.BBInterface;

            leaf name {
                type string;
            }

            leaf ipv4-address {
                type string;
            }

            leaf ipv4-prefix-length {
                type uint8 {
                    range "0..32";
                }
                default "30";
            }

            leaf ipv6-address {
                type string;
            }

            leaf ipv6-prefix-length {
                type uint8 {
                    range "0..128";
                }
            }

            container remote {
                leaf device {
                    type string;
                    mandatory true;
                }
                leaf interface {
                    type string;
                    mandatory true;
                }
            }

            leaf monitor-traffic {
                type boolean;
                default "false";
            }

            container dynstate {
                sw:dynstate;
                leaf pps {
                    type uint64;
                }
            }

            container state {
                config false;
                leaf rx-packets {
                    type uint64;
                }
                leaf pps {
                    type uint64;
                }
                leaf oper-status {
                    type enumeration {
                        enum up;
                        enum down;
                        enum unknown;
                    }
                }
            }
        }

        list ibgp-neighbor {
          key address;
          sw:rfs-transform sorespo.rfs.IbgpNeighbor;
          leaf address {
            type inet:ip-address;
          }
          leaf asn {
            // Need this one for IOS XR: router bgp <asn>
            type inet:as-number;
            mandatory true;
          }
          leaf description {
            type string;
            mandatory true;
          }
        }

        list vrf {
          key name;
          sw:rfs-transform sorespo.rfs.Vrf;
          leaf name {
            type string;
          }
          leaf description {
            type string;
          }
          // TODO: compute RD in the layer above and use as key?!
          leaf id {
            type uint32;
            mandatory true;
          }
          leaf router-id {
            type uint32;
            mandatory true;
          }
          leaf asn {
            type inet:as-number;
            mandatory true;
          }
        }

        list vrf-interface {
            key "name";
            sw:rfs-transform sorespo.rfs.VrfInterface;
            leaf name {
                type string;
            }
            leaf description {
                type string;
            }
            leaf vrf {
                type string;
                description
                    "VRF name";
                mandatory true;
            }
            leaf ipv4-address {
                type inet:ipv4-address;
            }
            leaf ipv4-prefix-length {
                type uint8 {
                    range "1..31";
                }
                default "30";
            }
        }

    list ebgp-customer {
      key "vrf address";
      sw:rfs-transform sorespo.rfs.EbgpCustomer;
      leaf vrf {
        type string;
      }
      leaf address {
        type inet:ip-address;
      }
      leaf local-asn {
        type uint32;
        mandatory true;
      }
      leaf peer-asn {
        type uint32;
        mandatory true;
      }
      leaf description {
        type string;
      }
      leaf authentication-key {
        type string;
        mandatory true;
      }
    }
  }
}
