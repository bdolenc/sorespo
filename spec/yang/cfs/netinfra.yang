module netinfra {
  yang-version "1.1";
  namespace "http://example.com/netinfra";
  prefix "netinfra";
  description "Network Infrastructure";
  revision 2019-01-01 {
    description "test revision";
    reference "ref1";
  }
  import ietf-inet-types {
    prefix inet;
  }
  import stratoweave {
    prefix sw;
  }
  import ietf-yang-tmf-map {
    prefix tmf;
  }

  container netinfra {
    description "Network infrastructure";
    list router {
      description "Network Infrastructure Router";
      key name;

      sw:transform sorespo.cfs.Router;
      tmf:cfs-service "Router";

      leaf name {
        type string;
      }
      leaf id {
        type uint32;
        description "router id";
        mandatory true;
      }
      leaf type {
        type string;
        mandatory true;
      }
      leaf role {
        type string;
      }
      leaf asn {
        type inet:as-number;
        mandatory true;
      }
      leaf mock {
        type boolean;
        default false;
      }
      leaf approval-required {
        type boolean;
        default false;
      }
      container feature-flags {
        leaf runtime-schema-fetch {
          type boolean;
          default false;
        }
      }
    }

    list backbone-link {
      key "left-router left-interface right-router right-interface";

      sw:transform sorespo.cfs.BBLink;
      tmf:cfs-service "Backbone Link";

      leaf left-router {
        type string;
      }
      leaf left-interface {
        type string;
      }
      leaf right-router {
        type string;
      }
      leaf right-interface {
        type string;
      }
      leaf monitor-traffic {
        type boolean;
        default false;
      }
      container dynstate {
        sw:dynstate;
      }
      container state {
        config false;
        description
          "Operational state lifted from the underlying RFS backbone-interface entries.
           left-pps is the receive PPS measured on the left interface (traffic flowing right -> left);
           right-pps is the receive PPS measured on the right interface (traffic flowing left -> right).";
        leaf left-pps {
          type uint64;
        }
        leaf right-pps {
          type uint64;
        }
      }
    }
  }
}
